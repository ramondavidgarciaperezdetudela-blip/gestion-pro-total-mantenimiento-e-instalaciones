;;; Símbolos de planta de Gestión Pro Total para CADCraft: dibujos reconocibles de cada equipo
;;; (no cajas con letras). Unidades: metros. Cada símbolo se dibuja dentro de su bloque, centrado en 0,0.

(setq gs-pi 3.14159265358979)
(defun gs-rad (g) (* g (/ gs-pi 180.0)))

;; ── Primitivas ────────────────────────────────────────────────────────────────
(defun gs-l (x1 y1 x2 y2)
  (entmake (list (cons 0 "LINE") (cons 8 "0") (list 10 x1 y1 0.0) (list 11 x2 y2 0.0))))
(defun gs-p (pts cerrada)
  (entmake (append (list (cons 0 "LWPOLYLINE") (cons 100 "AcDbEntity") (cons 8 "0") (cons 100 "AcDbPolyline")
                         (cons 90 (length pts)) (cons 70 (if cerrada 1 0)))
                   (mapcar '(lambda (p) (list 10 (car p) (cadr p))) pts))))
(defun gs-r (x1 y1 x2 y2) (gs-p (list (list x1 y1) (list x2 y1) (list x2 y2) (list x1 y2)) T))
(defun gs-c (x y r) (entmake (list (cons 0 "CIRCLE") (cons 8 "0") (list 10 x y 0.0) (cons 40 r))))
(defun gs-a (x y r a1 a2)
  (entmake (list (cons 0 "ARC") (cons 8 "0") (list 10 x y 0.0) (cons 40 r) (cons 50 (gs-rad a1)) (cons 51 (gs-rad a2)))))
(defun gs-t (x y h txt)
  (entmake (list (cons 0 "TEXT") (cons 8 "0") (list 10 x y 0.0) (list 11 x y 0.0) (cons 40 h) (cons 1 txt) (cons 72 1) (cons 73 2))))

;; ── Piezas reutilizables ──────────────────────────────────────────────────────
;; Ventilador axial: aro, buje y tres palas curvas.
(defun gs-vent (x y r / i a c)
  (setq c (list x y) i 0)
  (gs-c x y r) (gs-c x y (* 0.14 r))
  (repeat 3
    (setq a (* i 2.0943951))
    (gs-p (list (polar c a (* 0.16 r)) (polar c (+ a 0.30) (* 0.55 r)) (polar c (+ a 0.20) (* 0.92 r))
                (polar c (+ a 0.75) (* 0.80 r)) (polar c (+ a 0.85) (* 0.45 r)) (polar c (+ a 0.55) (* 0.16 r))) T)
    (setq i (1+ i))))
;; Ventilador centrífugo: voluta en espiral y rodete.
(defun gs-centrif (x y r / i)
  (gs-a x y r 0 270)
  (gs-p (list (list (+ x r) y) (list (+ x r) (- y (* 1.15 r))) (list x (- y (* 1.15 r))) (list x (- y r))) nil)
  (gs-c x y (* 0.55 r)) (gs-c x y (* 0.12 r))
  (setq i 0)
  (repeat 8 (gs-l (+ x (* 0.14 r (cos (* i 0.785398)))) (+ y (* 0.14 r (sin (* i 0.785398))))
                  (+ x (* 0.55 r (cos (+ 0.4 (* i 0.785398))))) (+ y (* 0.55 r (sin (+ 0.4 (* i 0.785398))))))
    (setq i (1+ i))))
;; Aletas del serpentín (líneas paralelas)
(defun gs-aletas (x1 y1 x2 y2 n vertical / i f)
  (setq i 1)
  (repeat (1- n)
    (setq f (/ (float i) n))
    (if vertical
      (gs-l (+ x1 (* f (- x2 x1))) y1 (+ x1 (* f (- x2 x1))) y2)
      (gs-l x1 (+ y1 (* f (- y2 y1))) x2 (+ y1 (* f (- y2 y1)))))
    (setq i (1+ i))))
;; Zigzag (serpentín de tubo, muelle)
(defun gs-zig (x1 x2 y n amp / pts i)
  (setq pts (list (list x1 y)) i 1)
  (repeat n
    (setq pts (append pts (list (list (+ x1 (* (- x2 x1) (/ (- i 0.5) n))) (+ y (if (= (rem i 2) 1) amp (- amp)))))))
    (setq i (1+ i)))
  (gs-p (append pts (list (list x2 y))) nil))
;; Válvula (dos triángulos enfrentados) con eje
(defun gs-valv (x y s / h)
  (setq h (* 0.6 s))
  (gs-p (list (list (- x s) (+ y h)) (list (- x s) (- y h)) (list (+ x s) (+ y h)) (list (+ x s) (- y h))) T)
  (gs-l (- x (* 1.4 s)) y (- x s) y) (gs-l (+ x s) y (+ x (* 1.4 s)) y))
;; Flecha desde (x1,y1) hacia (x2,y2)
(defun gs-flecha (x1 y1 x2 y2 / a c)
  (setq a (angle (list x1 y1) (list x2 y2)) c (* 0.35 (distance (list x1 y1) (list x2 y2))))
  (gs-l x1 y1 x2 y2)
  (gs-p (list (polar (list x2 y2) (+ a 2.8) c) (list x2 y2) (polar (list x2 y2) (- a 2.8) c)) nil))
;; Cápsula (depósito horizontal)
(defun gs-capsula (x1 y1 x2 y2 / r)
  (setq r (/ (- y2 y1) 2.0))
  (gs-l (+ x1 r) y1 (- x2 r) y1) (gs-l (+ x1 r) y2 (- x2 r) y2)
  (gs-a (+ x1 r) (+ y1 r) r 90 270) (gs-a (- x2 r) (+ y1 r) r -90 90))
;; Rejilla: cuadrado con lamas en diagonal
(defun gs-rejilla (hx hy / i)
  (gs-r (- hx) (- hy) hx hy) (gs-r (* -0.78 hx) (* -0.78 hy) (* 0.78 hx) (* 0.78 hy))
  (setq i -2)
  (repeat 5 (gs-l (* -0.78 hx) (* (* 0.39 i) hy) (* 0.78 hx) (* (+ (* 0.39 i) 0.78) hy)) (setq i (1+ i))))

;; ── Dibujo de cada equipo ─────────────────────────────────────────────────────
;; id = nombre del bloque (EQ-...), w y h = tamaño en metros.
(defun gs-dibuja (id w h / hx hy r)
  (setq hx (/ w 2.0) hy (/ h 2.0) r (* 0.9 (min hx hy)))
  (cond
    ;; ── Refrigeración ──
    ((= id "EQ-COMPRESOR")
     (gs-r (- hx) (- hy) hx hy) (gs-c (* -0.2 w) 0.0 (* 0.34 h)) (gs-c (* -0.2 w) 0.0 (* 0.12 h))
     (gs-r (* 0.15 w) (* -0.3 h) (* 0.42 w) (* 0.3 h)) (gs-l (* 0.15 w) 0.0 (* 0.42 w) 0.0)
     (gs-l (* 0.3 w) hy (* 0.3 w) (* 0.3 h)) (gs-l (* 0.05 w) hy (* 0.05 w) (* 0.34 h)))
    ((= id "EQ-CONDENSADOR")
     (gs-r (- hx) (- hy) hx hy) (gs-aletas (- hx) (- hy) (* -0.55 hx) hy 6 T)
     (gs-vent (* 0.22 hx) 0.0 (* 0.62 hy)) (gs-l (* -0.55 hx) (- hy) (* -0.55 hx) hy))
    ((= id "EQ-CONDENSADORA_AIRE")
     (gs-r (- hx) (- hy) hx hy) (gs-vent (* -0.45 hx) 0.0 (* 0.78 hy)) (gs-vent (* 0.45 hx) 0.0 (* 0.78 hy))
     (gs-aletas (- hx) (- hy) hx (- hy) 1 T) (gs-r (* -0.97 hx) (* -0.97 hy) (* 0.97 hx) (* 0.97 hy)))
    ((= id "EQ-CONDENSADORA_CENTRIFUGO")
     (gs-r (- hx) (- hy) hx hy) (gs-centrif (* -0.4 hx) (* 0.15 hy) (* 0.5 hy)) (gs-aletas (* 0.15 hx) (- hy) hx hy 7 T)
     (gs-l (* 0.15 hx) (- hy) (* 0.15 hx) hy))
    ((= id "EQ-CONDENSADORA_AGUA")
     (gs-r (- hx) (- hy) hx hy) (gs-zig (* -0.8 hx) (* 0.8 hx) (* 0.45 hy) 6 (* 0.22 hy)) (gs-zig (* -0.8 hx) (* 0.8 hx) (* -0.1 hy) 6 (* 0.22 hy))
     (gs-zig (* -0.8 hx) (* 0.8 hx) (* -0.65 hy) 6 (* 0.18 hy))
     (gs-flecha (- hx) (* 0.45 hy) (* -0.8 hx) (* 0.45 hy)) (gs-flecha (* 0.8 hx) (* -0.65 hy) hx (* -0.65 hy)))
    ((= id "EQ-CONDENSADORA_EVAPORATIVA")
     (gs-r (- hx) (- hy) hx hy) (gs-vent 0.0 (* 0.52 hy) (* 0.38 hy)) (gs-zig (* -0.85 hx) (* 0.85 hx) (* -0.12 hy) 8 (* 0.14 hy))
     (gs-l (* -0.85 hx) (* 0.12 hy) (* 0.85 hx) (* 0.12 hy)) (gs-l (* -0.85 hx) (* -0.72 hy) (* 0.85 hx) (* -0.72 hy))
     (gs-c (* -0.4 hx) (* -0.45 hy) (* 0.05 hy)) (gs-c 0.0 (* -0.5 hy) (* 0.05 hy)) (gs-c (* 0.4 hx) (* -0.45 hy) (* 0.05 hy)))
    ((= id "EQ-CONDENSADORA_SECA")
     (gs-r (- hx) (- hy) hx hy) (gs-aletas (- hx) (- hy) hx hy 10 T)
     (gs-vent (* -0.5 hx) 0.0 (* 0.42 hy)) (gs-vent (* 0.0 hx) 0.0 (* 0.42 hy)) (gs-vent (* 0.5 hx) 0.0 (* 0.42 hy)))
    ((= id "EQ-EVAPORADOR")
     (gs-r (- hx) (- hy) hx hy) (gs-aletas (- hx) (- hy) (* 0.1 hx) hy 8 T) (gs-vent (* 0.55 hx) 0.0 (* 0.6 hy))
     (gs-l (* 0.1 hx) (- hy) (* 0.1 hx) hy))
    ((= id "EQ-GRUPO_FRIO")
     (gs-r (- hx) (- hy) hx hy) (gs-c (* -0.55 hx) (* 0.3 hy) (* 0.28 hy)) (gs-c (* -0.55 hx) (* 0.3 hy) (* 0.1 hy))
     (gs-capsula (* -0.8 hx) (* -0.85 hy) (* 0.1 hx) (* -0.35 hy))
     (gs-aletas (* 0.25 hx) (- hy) hx hy 6 T) (gs-l (* 0.25 hx) (- hy) (* 0.25 hx) hy) (gs-vent (* 0.62 hx) 0.0 (* 0.4 hy)))
    ((= id "EQ-CENTRAL_FRIGORIFICA")
     (gs-r (- hx) (- hy) hx hy) (gs-c (* -0.6 hx) (* 0.2 hy) (* 0.28 hy)) (gs-c (* -0.2 hx) (* 0.2 hy) (* 0.28 hy)) (gs-c (* 0.2 hx) (* 0.2 hy) (* 0.28 hy))
     (gs-c (* -0.6 hx) (* 0.2 hy) (* 0.1 hy)) (gs-c (* -0.2 hx) (* 0.2 hy) (* 0.1 hy)) (gs-c (* 0.2 hx) (* 0.2 hy) (* 0.1 hy))
     (gs-capsula (* -0.8 hx) (* -0.8 hy) (* 0.45 hx) (* -0.35 hy)) (gs-l (* -0.85 hx) (* -0.12 hy) (* 0.5 hx) (* -0.12 hy))
     (gs-r (* 0.62 hx) (* -0.85 hy) (* 0.95 hx) (* 0.85 hy)) (gs-t (* 0.785 hx) 0.0 (* 0.2 hy) "CTL"))
    ((= id "EQ-CAMARA_FRIGORIFICA")
     (gs-r (- hx) (- hy) hx hy) (gs-r (* -0.92 hx) (* -0.92 hy) (* 0.92 hx) (* 0.92 hy))
     (gs-aletas (- hx) (- hy) (* -0.92 hx) hy 3 nil) (gs-l (- hx) (- hy) (* -0.92 hx) (* -0.92 hy))
     (gs-l (* 0.3 hx) (* -0.92 hy) (* 0.92 hx) (* -0.92 hy)) (gs-a (* 0.3 hx) (* -0.92 hy) (* 0.62 hx) 0 90)
     (gs-l (* 0.3 hx) (* -0.92 hy) (* 0.3 hx) (* -0.3 hy))
     (gs-r (* -0.6 hx) (* 0.55 hy) (* 0.2 hx) (* 0.85 hy)) (gs-vent (* -0.4 hx) (* 0.7 hy) (* 0.13 hy)) (gs-vent (* 0.0 hx) (* 0.7 hy) (* 0.13 hy)))
    ((= id "EQ-VENTILADOR") (gs-r (- hx) (- hy) hx hy) (gs-vent 0.0 0.0 r))
    ((= id "EQ-VALVULA_EXPANSION")
     (gs-valv 0.0 0.0 (* 0.6 hx)) (gs-l 0.0 0.0 0.0 (* 0.8 hy)) (gs-c 0.0 (* 0.8 hy) (* 0.14 hy)) (gs-p (list (list (* -0.5 hx) (* -0.9 hy)) (list (* 0.3 hx) (* 0.3 hy))) nil))
    ((= id "EQ-TUBERIA_REFRIGERANTE")
     (gs-l (- hx) 0.0 hx 0.0) (gs-flecha (* -0.3 hx) 0.0 (* 0.6 hx) 0.0) (gs-l (* 0.1 hx) (* -0.8 hy) (* 0.1 hx) (* 0.8 hy)))
    ((= id "EQ-DESHUMIDIFICADOR")
     (gs-r (- hx) (- hy) hx hy) (gs-p (list (list 0.0 (* 0.7 hy)) (list (* 0.35 hx) (* 0.05 hy)) (list 0.0 (* -0.1 hy)) (list (* -0.35 hx) (* 0.05 hy))) T)
     (gs-a 0.0 (* -0.1 hy) (* 0.35 hx) 180 360) (gs-aletas (- hx) (- hy) hx (* -0.6 hy) 3 nil))
    ((= id "EQ-VITRINA")
     (gs-r (- hx) (- hy) hx hy) (gs-r (* -0.94 hx) (* -0.8 hy) (* 0.94 hx) (* 0.6 hy)) (gs-aletas (* -0.94 hx) (* -0.8 hy) (* 0.94 hx) (* 0.6 hy) 3 nil)
     (gs-l (- hx) hy (* 0.94 hx) (* 0.6 hy)) (gs-aletas (- hx) (* 0.65 hy) hx hy 1 nil))
    ((= id "EQ-MURAL")
     (gs-r (- hx) (- hy) hx hy) (gs-r (* -0.97 hx) (* -0.6 hy) (* 0.97 hx) (* 0.6 hy)) (gs-aletas (- hx) (- hy) hx hy 12 T)
     (gs-flecha (* -0.5 hx) (* 0.3 hy) (* -0.5 hx) (* 0.9 hy)) (gs-flecha (* 0.5 hx) (* 0.3 hy) (* 0.5 hx) (* 0.9 hy)))
    ((= id "EQ-ARCON")
     (gs-r (- hx) (- hy) hx hy) (gs-r (* -0.9 hx) (* -0.75 hy) (* 0.9 hx) (* 0.75 hy)) (gs-l (- hx) hy (* 0.9 hx) (* 0.75 hy)) (gs-l hx hy (* 0.9 hx) (* 0.75 hy))
     (gs-t 0.0 0.0 (* 0.3 h) "*"))
    ((= id "EQ-ABATIDOR")
     (gs-r (- hx) (- hy) hx hy) (gs-r (* -0.8 hx) (* -0.8 hy) (* 0.8 hx) (* 0.8 hy)) (gs-vent 0.0 0.0 (* 0.5 hy))
     (gs-l (* -0.8 hx) (* 0.5 hy) (* -0.55 hx) (* 0.5 hy)) (gs-l (* 0.55 hx) (* -0.5 hy) (* 0.8 hx) (* -0.5 hy)))
    ((= id "EQ-BOTELLERO")
     (gs-r (- hx) (- hy) hx hy) (gs-r (* -0.96 hx) (* -0.8 hy) (* 0.96 hx) (* 0.8 hy))
     (gs-c (* -0.78 hx) 0.0 (* 0.12 hy)) (gs-c (* -0.52 hx) 0.0 (* 0.12 hy)) (gs-c (* -0.26 hx) 0.0 (* 0.12 hy)) (gs-c 0.0 0.0 (* 0.12 hy))
     (gs-c (* 0.26 hx) 0.0 (* 0.12 hy)) (gs-c (* 0.52 hx) 0.0 (* 0.12 hy)) (gs-c (* 0.78 hx) 0.0 (* 0.12 hy)))
    ((= id "EQ-RECIBIDOR")
     (gs-capsula (- hx) (* -0.5 hy) hx (* 0.5 hy)) (gs-l (* -0.5 hx) (* 0.5 hy) (* -0.5 hx) hy) (gs-l (* 0.5 hx) (- hy) (* 0.5 hx) (* -0.5 hy)) (gs-aletas (- hx) (* -0.5 hy) hx (* 0.5 hy) 2 nil))
    ((= id "EQ-SEPARADOR_ACEITE")
     (gs-c 0.0 0.0 (* 0.8 hy)) (gs-l 0.0 (* 0.8 hy) 0.0 hy) (gs-l (* 0.5 hx) (- hy) (* 0.5 hx) (* -0.8 hy)) (gs-l (* -0.5 hx) (* 0.8 hy) (* -0.5 hx) hy)
     (gs-zig (* -0.55 hx) (* 0.55 hx) 0.0 5 (* 0.25 hy)))
    ((= id "EQ-FILTRO_DESHIDRATADOR")
     (gs-p (list (list (- hx) 0.0) (list 0.0 (* 0.8 hy)) (list hx 0.0) (list 0.0 (* -0.8 hy))) T) (gs-l (* -0.5 hx) (* -0.4 hy) (* 0.5 hx) (* 0.4 hy)) (gs-l (* -0.5 hx) (* 0.4 hy) (* 0.5 hx) (* -0.4 hy)))
    ((= id "EQ-VISOR_LIQUIDO")
     (gs-c 0.0 0.0 (* 0.85 hx)) (gs-c 0.0 0.0 (* 0.45 hx)) (gs-l (* -1.0 hx) 0.0 (* -0.85 hx) 0.0) (gs-l (* 0.85 hx) 0.0 hx 0.0))
    ((= id "EQ-VALVULA_SOLENOIDE")
     (gs-valv 0.0 (* -0.15 hy) (* 0.6 hx)) (gs-l 0.0 (* -0.15 hy) 0.0 (* 0.35 hy)) (gs-r (* -0.4 hx) (* 0.35 hy) (* 0.4 hx) (* 0.95 hy)) (gs-p (list (list (* -0.25 hx) (* 0.45 hy)) (list (* 0.25 hx) (* 0.85 hy))) nil) (gs-p (list (list (* -0.25 hx) (* 0.85 hy)) (list (* 0.25 hx) (* 0.45 hy))) nil))
    ((= id "EQ-PRESOSTATO") (gs-c 0.0 0.0 (* 0.9 hx)) (gs-t 0.0 0.0 (* 0.7 hx) "P") (gs-l 0.0 (- (* 0.9 hx)) 0.0 (- hy)))
    ((= id "EQ-CONTROL_TEMPERATURA") (gs-c 0.0 0.0 (* 0.9 hx)) (gs-t 0.0 0.0 (* 0.7 hx) "T") (gs-l 0.0 (- (* 0.9 hx)) 0.0 (- hy)))

    ;; ── Climatización ──
    ((= id "EQ-EXTERIOR_CLIMA")
     (gs-r (- hx) (- hy) hx hy) (gs-vent (* -0.45 hx) 0.0 (* 0.8 hy)) (gs-aletas (* 0.1 hx) (- hy) hx hy 6 T) (gs-l (* 0.1 hx) (- hy) (* 0.1 hx) hy))
    ((= id "EQ-CASSETTE")
     (gs-r (- hx) (- hy) hx hy) (gs-r (* -0.8 hx) (* -0.8 hy) (* 0.8 hx) (* 0.8 hy)) (gs-c 0.0 0.0 (* 0.3 hx)) (gs-c 0.0 0.0 (* 0.12 hx))
     (gs-r (* -0.55 hx) (* 0.82 hy) (* 0.55 hx) (* 0.94 hy)) (gs-r (* -0.55 hx) (* -0.94 hy) (* 0.55 hx) (* -0.82 hy))
     (gs-r (* 0.82 hx) (* -0.55 hy) (* 0.94 hx) (* 0.55 hy)) (gs-r (* -0.94 hx) (* -0.55 hy) (* -0.82 hx) (* 0.55 hy))
     (gs-l (* -0.8 hx) (* -0.8 hy) (* -0.4 hx) (* -0.4 hy)) (gs-l (* 0.8 hx) (* 0.8 hy) (* 0.4 hx) (* 0.4 hy)) (gs-l (* -0.8 hx) (* 0.8 hy) (* -0.4 hx) (* 0.4 hy)) (gs-l (* 0.8 hx) (* -0.8 hy) (* 0.4 hx) (* -0.4 hy)))
    ((= id "EQ-CONDUCTOS")
     (gs-r (* -0.5 hx) (- hy) hx hy) (gs-p (list (list (- hx) (* 0.45 hy)) (list (* -0.5 hx) (- hy)) (list (* -0.5 hx) hy) (list (- hx) (* -0.45 hy))) T)
     (gs-vent (* 0.3 hx) 0.0 (* 0.6 hy)) (gs-flecha (* -0.98 hx) 0.0 (* -0.55 hx) 0.0))
    ((= id "EQ-CONSOLA_SUELO")
     (gs-r (- hx) (- hy) hx hy) (gs-aletas (* -0.8 hx) (- hy) (* 0.8 hx) hy 10 T) (gs-r (* -0.8 hx) (* -0.55 hy) (* 0.8 hx) (* 0.55 hy)) (gs-flecha 0.0 hy 0.0 (* 2.2 hy)))
    ((= id "EQ-SPLIT_PARED")
     (gs-r (- hx) (- hy) hx hy) (gs-l (- hx) (* -0.35 hy) hx (* -0.35 hy)) (gs-aletas (* -0.9 hx) (* -0.35 hy) (* 0.9 hx) (- hy) 1 T)
     (gs-aletas (* -0.9 hx) (- hy) (* 0.9 hx) (* -0.35 hy) 14 T) (gs-flecha (* 0.6 hx) (- hy) (* 0.6 hx) (* -2.2 hy)) (gs-flecha (* -0.6 hx) (- hy) (* -0.6 hx) (* -2.2 hy)))
    ((= id "EQ-FANCOIL")
     (gs-r (- hx) (- hy) hx hy) (gs-zig (* -0.95 hx) (* -0.05 hx) 0.0 6 (* 0.55 hy)) (gs-vent (* 0.5 hx) 0.0 (* 0.75 hy)) (gs-l (* -0.05 hx) (- hy) (* -0.05 hx) hy))
    ((= id "EQ-RECUPERADOR")
     (gs-r (- hx) (- hy) hx hy) (gs-p (list (list (* -0.6 hx) (* 0.6 hy)) (list (* 0.6 hx) (* -0.6 hy))) nil) (gs-p (list (list (* -0.6 hx) (* -0.6 hy)) (list (* 0.6 hx) (* 0.6 hy))) nil)
     (gs-p (list (list (* -0.6 hx) (* 0.6 hy)) (list (* 0.6 hx) (* 0.6 hy)) (list (* 0.6 hx) (* -0.6 hy)) (list (* -0.6 hx) (* -0.6 hy))) T)
     (gs-flecha (- hx) (* 0.6 hy) (* -0.6 hx) (* 0.6 hy)) (gs-flecha (* 0.6 hx) (* 0.6 hy) hx (* 0.6 hy)) (gs-flecha (- hx) (* -0.6 hy) (* -0.6 hx) (* -0.6 hy)) (gs-flecha (* 0.6 hx) (* -0.6 hy) hx (* -0.6 hy)))

    ;; ── Ventilación ──
    ((= id "EQ-REJILLA_IMPULSION") (gs-rejilla hx hy) (gs-flecha 0.0 0.0 (* 0.6 hx) (* 0.6 hy)))
    ((= id "EQ-REJILLA_RETORNO") (gs-rejilla hx hy) (gs-flecha (* 0.6 hx) (* 0.6 hy) 0.0 0.0))
    ((= id "EQ-REJILLA_EXTRACCION") (gs-rejilla hx hy) (gs-l (* -0.5 hx) (* -0.5 hy) (* 0.5 hx) (* 0.5 hy)) (gs-l (* -0.5 hx) (* 0.5 hy) (* 0.5 hx) (* -0.5 hy)))
    ((= id "EQ-DIFUSOR_CIRCULAR")
     (gs-r (- hx) (- hy) hx hy) (gs-c 0.0 0.0 (* 0.9 hx)) (gs-c 0.0 0.0 (* 0.62 hx)) (gs-c 0.0 0.0 (* 0.3 hx)) (gs-l (- hx) 0.0 hx 0.0) (gs-l 0.0 (- hy) 0.0 hy))
    ((= id "EQ-DIFUSOR_LINEAL")
     (gs-r (- hx) (- hy) hx hy) (gs-l (* -0.95 hx) (* 0.4 hy) (* 0.95 hx) (* 0.4 hy)) (gs-l (* -0.95 hx) (* -0.4 hy) (* 0.95 hx) (* -0.4 hy)) (gs-l (* -0.95 hx) 0.0 (* 0.95 hx) 0.0))
    ((= id "EQ-BOCA_IMPULSION") (gs-c 0.0 0.0 (* 0.9 hx)) (gs-c 0.0 0.0 (* 0.5 hx)) (gs-flecha 0.0 0.0 (* 0.75 hx) (* 0.75 hy)))
    ((= id "EQ-BOCA_RETORNO") (gs-c 0.0 0.0 (* 0.9 hx)) (gs-c 0.0 0.0 (* 0.5 hx)) (gs-flecha (* 0.75 hx) (* 0.75 hy) 0.0 0.0))
    ((= id "EQ-VENTILADOR_EXTRACCION") (gs-r (- hx) (- hy) hx hy) (gs-vent 0.0 0.0 r) (gs-flecha (* 0.7 hx) (* -0.9 hy) (* 0.7 hx) (* 0.45 hy)))
    ((= id "EQ-VENTILADOR_IMPULSION") (gs-r (- hx) (- hy) hx hy) (gs-vent 0.0 0.0 r) (gs-flecha (* -0.7 hx) (* 0.45 hy) (* -0.7 hx) (* -0.9 hy)))
    ((= id "EQ-UVT")
     (gs-r (- hx) (- hy) hx hy) (gs-centrif (* -0.35 hx) 0.0 (* 0.6 hy)) (gs-r (* 0.2 hx) (* -0.6 hy) (* 0.9 hx) (* 0.6 hy)) (gs-aletas (* 0.2 hx) (* -0.6 hy) (* 0.9 hx) (* 0.6 hy) 5 T))
    ((= id "EQ-COMPUERTA_CORTAFUEGO")
     (gs-r (- hx) (- hy) hx hy) (gs-l (* -0.8 hx) (* -0.8 hy) (* 0.8 hx) (* 0.8 hy)) (gs-l (* -0.8 hx) (* 0.8 hy) (* 0.8 hx) (* -0.8 hy)) (gs-t 0.0 (* 0.6 hy) (* 0.28 h) "EI"))
    ((= id "EQ-SILENCIADOR")
     (gs-r (- hx) (- hy) hx hy) (gs-r (* -0.7 hx) (* -0.8 hy) (* 0.7 hx) (* -0.5 hy)) (gs-r (* -0.7 hx) (* -0.15 hy) (* 0.7 hx) (* 0.15 hy)) (gs-r (* -0.7 hx) (* 0.5 hy) (* 0.7 hx) (* 0.8 hy))
     (gs-flecha (* -1.0 hx) 0.0 (* -0.75 hx) 0.0))
    ((= id "EQ-CAJA_TOMA") (gs-r (- hx) (- hy) hx hy) (gs-c 0.0 0.0 (* 0.55 hx)) (gs-c (* -0.2 hx) 0.0 (* 0.08 hx)) (gs-c (* 0.2 hx) 0.0 (* 0.08 hx)) (gs-l (* -0.55 hx) (* -0.9 hy) (* 0.55 hx) (* -0.9 hy)))
    ((= id "EQ-EXTRACTOR_EOLICO") (gs-c 0.0 0.0 hx) (gs-c 0.0 0.0 (* 0.2 hx)) (gs-a 0.0 0.0 (* 0.65 hx) 0 90) (gs-a 0.0 0.0 (* 0.65 hx) 120 210) (gs-a 0.0 0.0 (* 0.65 hx) 240 330))

    ;; ── Eléctrico (simbología UNE/IEC) ──
    ((= id "EQ-CUADRO_ELECTRICO")
     (gs-r (- hx) (- hy) hx hy) (gs-r (* -0.92 hx) (* -0.7 hy) (* 0.92 hx) (* 0.7 hy)) (gs-aletas (* -0.92 hx) (* -0.7 hy) (* 0.92 hx) (* 0.7 hy) 6 T)
     (gs-l (- hx) (- hy) hx hy) (gs-l (- hx) hy hx (- hy)))
    ((= id "EQ-MAGNETOTERMICO")
     (gs-r (- hx) (- hy) hx hy) (gs-l (* -0.7 hx) 0.0 (* -0.25 hx) 0.0) (gs-l (* -0.25 hx) 0.0 (* 0.2 hx) (* 0.6 hy)) (gs-l (* 0.3 hx) 0.0 (* 0.7 hx) 0.0)
     (gs-c (* -0.25 hx) 0.0 (* 0.06 hx)) (gs-p (list (list (* 0.3 hx) (* 0.4 hy)) (list (* 0.5 hx) (* -0.4 hy)) (list (* 0.65 hx) (* 0.4 hy))) nil))
    ((= id "EQ-DIFERENCIAL")
     (gs-r (- hx) (- hy) hx hy) (gs-l (* -0.7 hx) 0.0 (* -0.25 hx) 0.0) (gs-l (* -0.25 hx) 0.0 (* 0.2 hx) (* 0.6 hy)) (gs-l (* 0.3 hx) 0.0 (* 0.7 hx) 0.0)
     (gs-c 0.0 (* -0.45 hy) (* 0.25 hy)) (gs-t 0.0 (* -0.45 hy) (* 0.22 hy) "Δ"))
    ((= id "EQ-CONTACTOR")
     (gs-r (- hx) (- hy) hx hy) (gs-r (* -0.6 hx) (* -0.45 hy) (* -0.1 hx) (* 0.45 hy)) (gs-t (* -0.35 hx) 0.0 (* 0.4 hy) "A") (gs-l (* 0.2 hx) (- hy) (* 0.2 hx) (* -0.3 hy)) (gs-l (* 0.2 hx) (* -0.3 hy) (* 0.55 hx) (* 0.3 hy)) (gs-l (* 0.55 hx) (* 0.3 hy) (* 0.55 hx) hy))
    ((= id "EQ-GUARDAMOTOR")
     (gs-r (- hx) (- hy) hx hy) (gs-c (* 0.4 hx) 0.0 (* 0.4 hy)) (gs-t (* 0.4 hx) 0.0 (* 0.4 hy) "M") (gs-l (* -0.9 hx) 0.0 (* 0.0 hx) 0.0) (gs-p (list (list (* -0.5 hx) (* 0.4 hy)) (list (* -0.35 hx) (* -0.4 hy)) (list (* -0.2 hx) (* 0.4 hy))) nil))
    ((= id "EQ-VARIADOR")
     (gs-r (- hx) (- hy) hx hy) (gs-l (- hx) 0.0 hx 0.0) (gs-p (list (list (* -0.8 hx) (* 0.45 hy)) (list (* -0.4 hx) (* 0.45 hy)) (list (* -0.2 hx) (* 0.75 hy)) (list 0.0 (* 0.15 hy)) (list (* 0.2 hx) (* 0.75 hy)) (list (* 0.4 hx) (* 0.45 hy)) (list (* 0.8 hx) (* 0.45 hy))) nil)
     (gs-t (* -0.5 hx) (* -0.5 hy) (* 0.3 hy) "~") (gs-t (* 0.5 hx) (* -0.5 hy) (* 0.3 hy) "~"))
    ((= id "EQ-AUTOMATA")
     (gs-r (- hx) (- hy) hx hy) (gs-t 0.0 0.0 (* 0.3 hy) "PLC") (gs-aletas (* -0.9 hx) (- hy) (* 0.9 hx) (* -0.6 hy) 8 T) (gs-aletas (* -0.9 hx) (* 0.6 hy) (* 0.9 hx) hy 8 T))
    ((= id "EQ-CABLEADO") (gs-l (- hx) 0.0 hx 0.0) (gs-l (* -0.3 hx) (* -0.5 hy) (* -0.1 hx) (* 0.5 hy)) (gs-l (* 0.0 hx) (* -0.5 hy) (* 0.2 hx) (* 0.5 hy)) (gs-l (* 0.3 hx) (* -0.5 hy) (* 0.5 hx) (* 0.5 hy)))
    ((= id "EQ-TOMA_CORRIENTE")
     (gs-c 0.0 0.0 (* 0.6 hx)) (gs-l (- hx) (* -0.0 hy) hx 0.0) (gs-l (- hx) (- hy) hx (- hy)) (gs-a 0.0 0.0 (* 0.6 hx) 0 180) (gs-l 0.0 (* 0.6 hy) 0.0 hy))
    ((= id "EQ-INTERRUPTOR")
     (gs-c 0.0 0.0 (* 0.35 hx)) (gs-l (* 0.2 hx) (* 0.2 hy) (* 0.85 hx) (* 0.85 hy)) (gs-l (* 0.65 hx) (* 0.85 hy) (* 0.85 hx) (* 0.65 hy)) (gs-l (* -0.7 hx) (* -0.0 hy) (* -0.35 hx) 0.0))
    ((= id "EQ-LUMINARIA")
     (gs-r (- hx) (- hy) hx hy) (gs-l (* -0.85 hx) 0.0 (* 0.85 hx) 0.0) (gs-l (* -0.85 hx) (* 0.4 hy) (* -0.85 hx) (* -0.4 hy)) (gs-l (* 0.85 hx) (* 0.4 hy) (* 0.85 hx) (* -0.4 hy)))
    ((= id "EQ-PUESTA_TIERRA")
     (gs-l 0.0 hy 0.0 (* 0.1 hy)) (gs-l (* -0.7 hx) (* 0.1 hy) (* 0.7 hx) (* 0.1 hy)) (gs-l (* -0.45 hx) (* -0.3 hy) (* 0.45 hx) (* -0.3 hy)) (gs-l (* -0.2 hx) (* -0.7 hy) (* 0.2 hx) (* -0.7 hy)))

    ;; ── Seguridad ──
    ((= id "EQ-VALVULA_SEGURIDAD")
     (gs-valv 0.0 (* -0.2 hy) (* 0.55 hx)) (gs-l 0.0 (* -0.2 hy) 0.0 (* 0.2 hy)) (gs-zig (* -0.5 hx) (* 0.5 hx) (* 0.0 hy) 1 0.0) (gs-p (list (list 0.0 (* 0.2 hy)) (list (* 0.3 hx) (* 0.35 hy)) (list (* -0.3 hx) (* 0.5 hy)) (list (* 0.3 hx) (* 0.65 hy)) (list (* -0.3 hx) (* 0.8 hy)) (list 0.0 hy)) nil))
    ((= id "EQ-DETECTOR_FUGAS")
     (gs-c 0.0 0.0 (* 0.9 hx)) (gs-p (list (list (* -0.6 hx) (* 0.2 hy)) (list (* -0.3 hx) (* 0.45 hy)) (list 0.0 (* 0.2 hy)) (list (* 0.3 hx) (* 0.45 hy)) (list (* 0.6 hx) (* 0.2 hy))) nil)
     (gs-t 0.0 (* -0.3 hy) (* 0.5 hx) "GAS"))
    ((= id "EQ-ALARMA_CAMARA")
     (gs-c 0.0 0.0 (* 0.9 hx)) (gs-a 0.0 (* -0.1 hy) (* 0.5 hx) 0 180) (gs-l (* -0.5 hx) (* -0.1 hy) (* 0.5 hx) (* -0.1 hy)) (gs-c 0.0 (* -0.3 hy) (* 0.1 hx)) (gs-l 0.0 (* 0.4 hy) 0.0 (* 0.5 hy)))
    ((= id "EQ-PULSADOR_EMERGENCIA")
     (gs-r (- hx) (- hy) hx hy) (gs-c 0.0 0.0 (* 0.7 hx)) (gs-c 0.0 0.0 (* 0.4 hx)) (gs-l (* -0.28 hx) (* -0.28 hy) (* 0.28 hx) (* 0.28 hy)) (gs-l (* -0.28 hx) (* 0.28 hy) (* 0.28 hx) (* -0.28 hy)))
    ((= id "EQ-PARO_EMERGENCIA")
     (gs-p (list (list (* -0.4 hx) hy) (list (* 0.4 hx) hy) (list hx (* 0.4 hy)) (list hx (* -0.4 hy)) (list (* 0.4 hx) (- hy)) (list (* -0.4 hx) (- hy)) (list (- hx) (* -0.4 hy)) (list (- hx) (* 0.4 hy))) T) (gs-t 0.0 0.0 (* 0.28 hx) "STOP"))
    ((= id "EQ-EXTRACCION_EMERGENCIA")
     (gs-r (- hx) (- hy) hx hy) (gs-vent 0.0 0.0 (* 0.85 r)) (gs-t (* 0.65 hx) (* 0.7 hy) (* 0.3 hx) "E"))
    ((= id "EQ-EXTINTOR")
     (gs-c 0.0 0.0 (* 0.85 hx)) (gs-c 0.0 0.0 (* 0.4 hx)) (gs-p (list (list (* -0.2 hx) (* 0.4 hy)) (list (* 0.2 hx) (* 0.4 hy)) (list 0.0 (* 0.9 hy))) T) (gs-t 0.0 (* -0.1 hy) (* 0.35 hx) "EX"))
    ((= id "EQ-DETECTOR_HUMO")
     (gs-c 0.0 0.0 (* 0.9 hx)) (gs-c 0.0 0.0 (* 0.6 hx)) (gs-t 0.0 0.0 (* 0.6 hx) "S"))
    ((= id "EQ-LUZ_EMERGENCIA")
     (gs-r (- hx) (- hy) hx hy) (gs-t 0.0 0.0 (* 0.7 hy) "E") (gs-flecha (* 0.5 hx) (* 0.6 hy) (* 0.9 hx) (* 1.4 hy)) (gs-flecha (* -0.5 hx) (* 0.6 hy) (* -0.9 hx) (* 1.4 hy)))
    ((= id "EQ-SENALIZACION")
     (gs-p (list (list 0.0 hy) (list hx (- hy)) (list (- hx) (- hy))) T) (gs-l 0.0 (* 0.45 hy) 0.0 (* -0.25 hy)) (gs-c 0.0 (* -0.6 hy) (* 0.06 hy)))

    ;; ── Estructura ──
    ((= id "EQ-PILAR") (gs-r (- hx) (- hy) hx hy) (gs-l (- hx) (- hy) hx hy) (gs-l (- hx) hy hx (- hy)))
    ((= id "EQ-PUERTA")
     (gs-r (- hx) (- hy) hx hy) (gs-l (- hx) hy (- hx) (+ hy w)) (gs-a (- hx) hy w 0 90))
    ((= id "EQ-VENTANA")
     (gs-r (- hx) (- hy) hx hy) (gs-l (- hx) 0.0 hx 0.0) (gs-l (* -0.5 hx) (- hy) (* -0.5 hx) hy) (gs-l (* 0.5 hx) (- hy) (* 0.5 hx) hy))
    ((= id "EQ-DESAGUE")
     (gs-r (- hx) (- hy) hx hy) (gs-c 0.0 0.0 (* 0.8 hx)) (gs-l (* -0.55 hx) (* -0.55 hy) (* 0.55 hx) (* 0.55 hy)) (gs-l (* -0.55 hx) (* 0.55 hy) (* 0.55 hx) (* -0.55 hy)) (gs-l (- hx) 0.0 hx 0.0))
    ;; Cualquier otro (por si se añade al catálogo): caja con cruz
    (T (gs-r (- hx) (- hy) hx hy) (gs-l (- hx) (- hy) hx hy) (gs-l (- hx) hy hx (- hy))))
  (princ))

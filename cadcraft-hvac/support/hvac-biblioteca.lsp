;;; Generado por scripts/gen-cadcraft-hvac.mjs — no editar a mano.
;;; Biblioteca de equipos de Gestión Pro Total para CADCraft (unidades: metros).

(defun gpt-capa (nombre color) (gpt-nueva-capa nombre color))

(defun gpt-def-bloque (nombre w h forzar / k)
  ;; Símbolos pequeños (válvulas, instrumentos, mecanismos) se dibujan a 0,60 m como mínimo para que se vean en el plano.
  (if (or forzar (not (tblsearch "BLOCK" nombre)))
    (progn
      (setq k (/ 0.6 (max w h)))
      (if (< k 1.0) (setq k 1.0))
      (entmake (list (cons 0 "BLOCK") (cons 2 nombre) (cons 70 0) (list 10 0.0 0.0 0.0)))
      (gs-dibuja nombre (* w k) (* h k))
      (entmake (list (cons 0 "ENDBLK"))))))

(setq *gpt-giro* 0.0)
(setq *gpt-equipos* (list
  (list "EQ-COMPRESOR" 1.0000 0.8000 "EQUIPO-REFRIGERACION")
  (list "EQ-CONDENSADOR" 1.2000 0.8000 "EQUIPO-REFRIGERACION")
  (list "EQ-CONDENSADORA_AIRE" 1.4000 0.9000 "EQUIPO-REFRIGERACION")
  (list "EQ-CONDENSADORA_CENTRIFUGO" 1.4000 0.9000 "EQUIPO-REFRIGERACION")
  (list "EQ-CONDENSADORA_AGUA" 1.0000 0.7000 "EQUIPO-REFRIGERACION")
  (list "EQ-CONDENSADORA_EVAPORATIVA" 1.6000 1.4000 "EQUIPO-REFRIGERACION")
  (list "EQ-CONDENSADORA_SECA" 1.6000 0.9000 "EQUIPO-REFRIGERACION")
  (list "EQ-EVAPORADOR" 1.0000 0.6000 "EQUIPO-REFRIGERACION")
  (list "EQ-GRUPO_FRIO" 1.8000 1.2000 "EQUIPO-REFRIGERACION")
  (list "EQ-CENTRAL_FRIGORIFICA" 3.0000 1.5000 "EQUIPO-REFRIGERACION")
  (list "EQ-CAMARA_FRIGORIFICA" 3.0000 3.0000 "EQUIPO-REFRIGERACION")
  (list "EQ-VENTILADOR" 0.6000 0.6000 "EQUIPO-REFRIGERACION")
  (list "EQ-VALVULA_EXPANSION" 0.3000 0.3000 "EQUIPO-REFRIGERACION")
  (list "EQ-TUBERIA_REFRIGERANTE" 0.2000 0.2000 "EQUIPO-REFRIGERACION")
  (list "EQ-DESHUMIDIFICADOR" 0.5000 0.4000 "EQUIPO-REFRIGERACION")
  (list "EQ-VITRINA" 2.5000 1.0000 "EQUIPO-REFRIGERACION")
  (list "EQ-MURAL" 3.7500 0.9000 "EQUIPO-REFRIGERACION")
  (list "EQ-ARCON" 1.5000 0.7000 "EQUIPO-REFRIGERACION")
  (list "EQ-ABATIDOR" 0.8000 0.8000 "EQUIPO-REFRIGERACION")
  (list "EQ-BOTELLERO" 1.5000 0.6000 "EQUIPO-REFRIGERACION")
  (list "EQ-RECIBIDOR" 0.5000 0.5000 "EQUIPO-REFRIGERACION")
  (list "EQ-SEPARADOR_ACEITE" 0.4000 0.4000 "EQUIPO-REFRIGERACION")
  (list "EQ-FILTRO_DESHIDRATADOR" 0.2000 0.2000 "EQUIPO-REFRIGERACION")
  (list "EQ-VISOR_LIQUIDO" 0.1500 0.1500 "EQUIPO-REFRIGERACION")
  (list "EQ-VALVULA_SOLENOIDE" 0.2000 0.2000 "EQUIPO-REFRIGERACION")
  (list "EQ-PRESOSTATO" 0.2000 0.2000 "EQUIPO-REFRIGERACION")
  (list "EQ-CONTROL_TEMPERATURA" 0.2000 0.2000 "EQUIPO-REFRIGERACION")
  (list "EQ-EXTERIOR_CLIMA" 1.0000 0.4000 "EQUIPO-CLIMA")
  (list "EQ-CASSETTE" 0.9000 0.9000 "EQUIPO-CLIMA")
  (list "EQ-CONDUCTOS" 1.2000 0.6000 "EQUIPO-CLIMA")
  (list "EQ-CONSOLA_SUELO" 1.0000 0.2500 "EQUIPO-CLIMA")
  (list "EQ-SPLIT_PARED" 0.9000 0.2000 "EQUIPO-CLIMA")
  (list "EQ-FANCOIL" 0.8000 0.3000 "EQUIPO-CLIMA")
  (list "EQ-RECUPERADOR" 1.2000 0.8000 "EQUIPO-CLIMA")
  (list "EQ-REJILLA_IMPULSION" 0.4000 0.4000 "EQUIPO-VENTILACION")
  (list "EQ-REJILLA_RETORNO" 0.4000 0.4000 "EQUIPO-VENTILACION")
  (list "EQ-REJILLA_EXTRACCION" 0.4000 0.4000 "EQUIPO-VENTILACION")
  (list "EQ-DIFUSOR_CIRCULAR" 0.5000 0.5000 "EQUIPO-VENTILACION")
  (list "EQ-DIFUSOR_LINEAL" 1.2000 0.2000 "EQUIPO-VENTILACION")
  (list "EQ-BOCA_IMPULSION" 0.3000 0.3000 "EQUIPO-VENTILACION")
  (list "EQ-BOCA_RETORNO" 0.3000 0.3000 "EQUIPO-VENTILACION")
  (list "EQ-VENTILADOR_EXTRACCION" 0.6000 0.6000 "EQUIPO-VENTILACION")
  (list "EQ-VENTILADOR_IMPULSION" 0.6000 0.6000 "EQUIPO-VENTILACION")
  (list "EQ-UVT" 1.6000 0.9000 "EQUIPO-VENTILACION")
  (list "EQ-COMPUERTA_CORTAFUEGO" 0.5000 0.5000 "EQUIPO-VENTILACION")
  (list "EQ-SILENCIADOR" 0.8000 0.4000 "EQUIPO-VENTILACION")
  (list "EQ-CAJA_TOMA" 0.6000 0.6000 "EQUIPO-VENTILACION")
  (list "EQ-EXTRACTOR_EOLICO" 0.5000 0.5000 "EQUIPO-VENTILACION")
  (list "EQ-CUADRO_ELECTRICO" 0.8000 0.3000 "EQUIPO-ELECTRICO")
  (list "EQ-MAGNETOTERMICO" 0.3000 0.2000 "EQUIPO-ELECTRICO")
  (list "EQ-DIFERENCIAL" 0.3000 0.2000 "EQUIPO-ELECTRICO")
  (list "EQ-CONTACTOR" 0.2500 0.2000 "EQUIPO-ELECTRICO")
  (list "EQ-GUARDAMOTOR" 0.2500 0.2000 "EQUIPO-ELECTRICO")
  (list "EQ-VARIADOR" 0.4000 0.3000 "EQUIPO-ELECTRICO")
  (list "EQ-AUTOMATA" 0.4000 0.3000 "EQUIPO-ELECTRICO")
  (list "EQ-CABLEADO" 0.1000 0.1000 "EQUIPO-ELECTRICO")
  (list "EQ-TOMA_CORRIENTE" 0.2000 0.2000 "EQUIPO-ELECTRICO")
  (list "EQ-INTERRUPTOR" 0.2000 0.2000 "EQUIPO-ELECTRICO")
  (list "EQ-LUMINARIA" 1.2000 0.2000 "EQUIPO-ELECTRICO")
  (list "EQ-PUESTA_TIERRA" 0.4000 0.4000 "EQUIPO-ELECTRICO")
  (list "EQ-VALVULA_SEGURIDAD" 0.2000 0.2000 "EQUIPO-SEGURIDAD")
  (list "EQ-DETECTOR_FUGAS" 0.2000 0.2000 "EQUIPO-SEGURIDAD")
  (list "EQ-ALARMA_CAMARA" 0.2000 0.2000 "EQUIPO-SEGURIDAD")
  (list "EQ-PULSADOR_EMERGENCIA" 0.2000 0.2000 "EQUIPO-SEGURIDAD")
  (list "EQ-PARO_EMERGENCIA" 0.2000 0.2000 "EQUIPO-SEGURIDAD")
  (list "EQ-EXTRACCION_EMERGENCIA" 0.6000 0.6000 "EQUIPO-SEGURIDAD")
  (list "EQ-EXTINTOR" 0.3000 0.3000 "EQUIPO-SEGURIDAD")
  (list "EQ-DETECTOR_HUMO" 0.2000 0.2000 "EQUIPO-SEGURIDAD")
  (list "EQ-LUZ_EMERGENCIA" 0.3000 0.1500 "EQUIPO-SEGURIDAD")
  (list "EQ-SENALIZACION" 0.2000 0.2000 "EQUIPO-SEGURIDAD")
  (list "EQ-PILAR" 0.4000 0.4000 "EQUIPO-ESTRUCTURA")
  (list "EQ-PUERTA" 1.0000 0.1500 "EQUIPO-ESTRUCTURA")
  (list "EQ-VENTANA" 1.2000 0.1500 "EQUIPO-ESTRUCTURA")
  (list "EQ-DESAGUE" 0.2000 0.2000 "EQUIPO-ESTRUCTURA")
))

;; Planos que vienen de Gestión Pro Total traen los equipos como cajas: se cambian por los símbolos reales.
(defun gpt-refrescar-bloques (/ d)
  (foreach d *gpt-equipos*
    (if (tblsearch "BLOCK" (car d)) (gpt-def-bloque (car d) (cadr d) (caddr d) T)))
  (princ))

(defun gpt-capas ()
  (gpt-capa "EQUIPO-REFRIGERACION" 4)
  (gpt-capa "EQUIPO-CLIMA" 30)
  (gpt-capa "EQUIPO-VENTILACION" 3)
  (gpt-capa "EQUIPO-ELECTRICO" 2)
  (gpt-capa "EQUIPO-SEGURIDAD" 1)
  (gpt-capa "EQUIPO-ESTRUCTURA" 6)
  (princ))

(defun gpt-colocar (id / d p g)
  (gpt-capas)
  (setq d (assoc id *gpt-equipos*))
  (gpt-def-bloque id (cadr d) (caddr d) nil)
  (initget "Giro")
  (while (setq p (getpoint (strcat "\nPunto de colocación de " id " [Giro " (rtos (* *gpt-giro* (/ 180.0 3.14159265)) 2 0) "°] (Intro para terminar): ")))
    (if (= p "Giro")
      (progn (setq g (getangle "\nGiro en grados: ")) (if g (setq *gpt-giro* g)))
      (progn
        (entmake (list (cons 0 "INSERT") (cons 8 (cadddr d)) (cons 2 id) (list 10 (car p) (cadr p) 0.0) (cons 41 1.0) (cons 42 1.0) (cons 43 1.0) (cons 50 *gpt-giro*)))
        (princ "\nColocado."))))
  (princ))

(defun c:EQ-COMPRESOR () (gpt-colocar "EQ-COMPRESOR"))
(defun c:EQ-CONDENSADOR () (gpt-colocar "EQ-CONDENSADOR"))
(defun c:EQ-CONDENSADORA_AIRE () (gpt-colocar "EQ-CONDENSADORA_AIRE"))
(defun c:EQ-CONDENSADORA_CENTRIFUGO () (gpt-colocar "EQ-CONDENSADORA_CENTRIFUGO"))
(defun c:EQ-CONDENSADORA_AGUA () (gpt-colocar "EQ-CONDENSADORA_AGUA"))
(defun c:EQ-CONDENSADORA_EVAPORATIVA () (gpt-colocar "EQ-CONDENSADORA_EVAPORATIVA"))
(defun c:EQ-CONDENSADORA_SECA () (gpt-colocar "EQ-CONDENSADORA_SECA"))
(defun c:EQ-EVAPORADOR () (gpt-colocar "EQ-EVAPORADOR"))
(defun c:EQ-GRUPO_FRIO () (gpt-colocar "EQ-GRUPO_FRIO"))
(defun c:EQ-CENTRAL_FRIGORIFICA () (gpt-colocar "EQ-CENTRAL_FRIGORIFICA"))
(defun c:EQ-CAMARA_FRIGORIFICA () (gpt-colocar "EQ-CAMARA_FRIGORIFICA"))
(defun c:EQ-VENTILADOR () (gpt-colocar "EQ-VENTILADOR"))
(defun c:EQ-VALVULA_EXPANSION () (gpt-colocar "EQ-VALVULA_EXPANSION"))
(defun c:EQ-TUBERIA_REFRIGERANTE () (gpt-colocar "EQ-TUBERIA_REFRIGERANTE"))
(defun c:EQ-DESHUMIDIFICADOR () (gpt-colocar "EQ-DESHUMIDIFICADOR"))
(defun c:EQ-VITRINA () (gpt-colocar "EQ-VITRINA"))
(defun c:EQ-MURAL () (gpt-colocar "EQ-MURAL"))
(defun c:EQ-ARCON () (gpt-colocar "EQ-ARCON"))
(defun c:EQ-ABATIDOR () (gpt-colocar "EQ-ABATIDOR"))
(defun c:EQ-BOTELLERO () (gpt-colocar "EQ-BOTELLERO"))
(defun c:EQ-RECIBIDOR () (gpt-colocar "EQ-RECIBIDOR"))
(defun c:EQ-SEPARADOR_ACEITE () (gpt-colocar "EQ-SEPARADOR_ACEITE"))
(defun c:EQ-FILTRO_DESHIDRATADOR () (gpt-colocar "EQ-FILTRO_DESHIDRATADOR"))
(defun c:EQ-VISOR_LIQUIDO () (gpt-colocar "EQ-VISOR_LIQUIDO"))
(defun c:EQ-VALVULA_SOLENOIDE () (gpt-colocar "EQ-VALVULA_SOLENOIDE"))
(defun c:EQ-PRESOSTATO () (gpt-colocar "EQ-PRESOSTATO"))
(defun c:EQ-CONTROL_TEMPERATURA () (gpt-colocar "EQ-CONTROL_TEMPERATURA"))
(defun c:EQ-EXTERIOR_CLIMA () (gpt-colocar "EQ-EXTERIOR_CLIMA"))
(defun c:EQ-CASSETTE () (gpt-colocar "EQ-CASSETTE"))
(defun c:EQ-CONDUCTOS () (gpt-colocar "EQ-CONDUCTOS"))
(defun c:EQ-CONSOLA_SUELO () (gpt-colocar "EQ-CONSOLA_SUELO"))
(defun c:EQ-SPLIT_PARED () (gpt-colocar "EQ-SPLIT_PARED"))
(defun c:EQ-FANCOIL () (gpt-colocar "EQ-FANCOIL"))
(defun c:EQ-RECUPERADOR () (gpt-colocar "EQ-RECUPERADOR"))
(defun c:EQ-REJILLA_IMPULSION () (gpt-colocar "EQ-REJILLA_IMPULSION"))
(defun c:EQ-REJILLA_RETORNO () (gpt-colocar "EQ-REJILLA_RETORNO"))
(defun c:EQ-REJILLA_EXTRACCION () (gpt-colocar "EQ-REJILLA_EXTRACCION"))
(defun c:EQ-DIFUSOR_CIRCULAR () (gpt-colocar "EQ-DIFUSOR_CIRCULAR"))
(defun c:EQ-DIFUSOR_LINEAL () (gpt-colocar "EQ-DIFUSOR_LINEAL"))
(defun c:EQ-BOCA_IMPULSION () (gpt-colocar "EQ-BOCA_IMPULSION"))
(defun c:EQ-BOCA_RETORNO () (gpt-colocar "EQ-BOCA_RETORNO"))
(defun c:EQ-VENTILADOR_EXTRACCION () (gpt-colocar "EQ-VENTILADOR_EXTRACCION"))
(defun c:EQ-VENTILADOR_IMPULSION () (gpt-colocar "EQ-VENTILADOR_IMPULSION"))
(defun c:EQ-UVT () (gpt-colocar "EQ-UVT"))
(defun c:EQ-COMPUERTA_CORTAFUEGO () (gpt-colocar "EQ-COMPUERTA_CORTAFUEGO"))
(defun c:EQ-SILENCIADOR () (gpt-colocar "EQ-SILENCIADOR"))
(defun c:EQ-CAJA_TOMA () (gpt-colocar "EQ-CAJA_TOMA"))
(defun c:EQ-EXTRACTOR_EOLICO () (gpt-colocar "EQ-EXTRACTOR_EOLICO"))
(defun c:EQ-CUADRO_ELECTRICO () (gpt-colocar "EQ-CUADRO_ELECTRICO"))
(defun c:EQ-MAGNETOTERMICO () (gpt-colocar "EQ-MAGNETOTERMICO"))
(defun c:EQ-DIFERENCIAL () (gpt-colocar "EQ-DIFERENCIAL"))
(defun c:EQ-CONTACTOR () (gpt-colocar "EQ-CONTACTOR"))
(defun c:EQ-GUARDAMOTOR () (gpt-colocar "EQ-GUARDAMOTOR"))
(defun c:EQ-VARIADOR () (gpt-colocar "EQ-VARIADOR"))
(defun c:EQ-AUTOMATA () (gpt-colocar "EQ-AUTOMATA"))
(defun c:EQ-CABLEADO () (gpt-colocar "EQ-CABLEADO"))
(defun c:EQ-TOMA_CORRIENTE () (gpt-colocar "EQ-TOMA_CORRIENTE"))
(defun c:EQ-INTERRUPTOR () (gpt-colocar "EQ-INTERRUPTOR"))
(defun c:EQ-LUMINARIA () (gpt-colocar "EQ-LUMINARIA"))
(defun c:EQ-PUESTA_TIERRA () (gpt-colocar "EQ-PUESTA_TIERRA"))
(defun c:EQ-VALVULA_SEGURIDAD () (gpt-colocar "EQ-VALVULA_SEGURIDAD"))
(defun c:EQ-DETECTOR_FUGAS () (gpt-colocar "EQ-DETECTOR_FUGAS"))
(defun c:EQ-ALARMA_CAMARA () (gpt-colocar "EQ-ALARMA_CAMARA"))
(defun c:EQ-PULSADOR_EMERGENCIA () (gpt-colocar "EQ-PULSADOR_EMERGENCIA"))
(defun c:EQ-PARO_EMERGENCIA () (gpt-colocar "EQ-PARO_EMERGENCIA"))
(defun c:EQ-EXTRACCION_EMERGENCIA () (gpt-colocar "EQ-EXTRACCION_EMERGENCIA"))
(defun c:EQ-EXTINTOR () (gpt-colocar "EQ-EXTINTOR"))
(defun c:EQ-DETECTOR_HUMO () (gpt-colocar "EQ-DETECTOR_HUMO"))
(defun c:EQ-LUZ_EMERGENCIA () (gpt-colocar "EQ-LUZ_EMERGENCIA"))
(defun c:EQ-SENALIZACION () (gpt-colocar "EQ-SENALIZACION"))
(defun c:EQ-PILAR () (gpt-colocar "EQ-PILAR"))
(defun c:EQ-PUERTA () (gpt-colocar "EQ-PUERTA"))
(defun c:EQ-VENTANA () (gpt-colocar "EQ-VENTANA"))
(defun c:EQ-DESAGUE () (gpt-colocar "EQ-DESAGUE"))
